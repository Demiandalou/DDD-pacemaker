# YixuanMeng_Req

## #1: initialize pacemaker model (Functional)
set values of AS,VS,AP,VP and basic cycles.

## #2: DDD pacemaker (Functional)
pacemaker state, which including all five parts.

## #3: URI part (Functional)
The pacemaker should not pace to increase the heart rate too high. So the minimum interval between a ventricular event and a ventricular pacing should be no less than URI.

## #4: init URI (Functional)
Initially set enterURI to be true.

## #5: Idle URI state (Functional)
When pacemaker is currently not in a URI period

## 6: Activate URI period (Functional)
Upon detecting a ventricular event, start a URI period until the period ends and allow VP to happen or another ventricular event happens before the period ends.

## 7: go back to idle URI (Functional)
after the count down of URI period end, VP can happen

## 8: Activated state of URI (Functional)
Indicates that less than URI time has passed after last ventricular event so no ventricular event should yet happen

## 9: count down for URI (Functional)
During the URI period, this transition serves as count down function until URI period ends or another ventricular event happens

## 10: reset when VS or VP (Functional)
During a URI period, another ventricular event is sensed, so the count down must be reset

## 11: LRI part (Functional)
The pacemaker should fulfil its intended use, which is maintaining a minimum ventricular rate. Therefore, the maximum interval between two consecutive ventricular events should be less or equal to LRI.

## 12: init LRI (Functional)
initialize count down variable tmpLRI, and initialize variables concerning AP

## 13: Idle LRI state (Functional)
when pacemaker is in a LRI period for no more than AEI time

## 14: reset LRI period (Functional)
if a ventricular event is detected in a LRI period, the count down variable should be reset

## 15: count down (Functional)
keep counting down in LRI period for no more than AEI time

## 16: AS transition (Functional)
if receive an AS in Idle state, go to activate state

## 17: Activate state of LRI (Functional)
Indicate that an atrial event has happened in a LRI period

## 18: AP in a LRI period (Functional)
If pacemaker enter active LRI state by generating an AP in a LRI period, set value of AP back to false

## 19: Last AVI time in LRI (Functional)
Do count down when atrial event has happened in a LRI period

## 20: LRI period ends (Functional)
At the end of LRI period, to keep minimum rate of ventricular events, pacemaker generate a VP

## 21: LRIVP state (Functional)
Indicates that a VP happened at the end of a LRI period

## 22: back to Idle (Functional)
The LRI period ends and VP generated, reset count down variable and restart from idle

## 23: remain AVI time (Functional)
If AEI time passed in LRI period, pacemaker generate an AP and enter active LRI state

## 24: reset on ventricular event (Functional)
if a ventricular event is detected before LRI period ends, reset LRI cycle.

## 25: AVI part (Functional)
AVI cycle ensures interval between an atrial event and a ventricular event is no more than AVI

## 26: init avi (Functional)
set VP variables to be false

## 27: Idle avi state (Functional)
Pacemaker stay in IdleAVI state when an AVI period has not been started

## 28: Active AVI state (Functional)
keep counting down in an AVI period

## 29: enter active AVI state (Functional)
start AVI period when an atrial event happens, set value of count down variable to be AVI

## 30: back to Idle AVI state (Functional)
when AVI period has not ended, but a ventricular event has been detected

## 31: count down in active AVI (Functional)
During an AVI period, if no VS or VP detected, keep counting down until AVI time passed

## 32: end of AVI period (Functional)
At the end of AVI period, give a VP to enforce maximum interval between A-V

## 33: CAVI state (Functional)
entered after an AVI period finished and VP generated

## 34: reset VP (Functional)
after generated VP at the end of AVI period, reset the value of VP to be false

## 35: VRP part (Functional)
Interval following a ventricular event during which ventricular senses would not inhibit or trigger pacing.

## 36: init VRP (Functional)
set VS to be false

## 37: Idle VRP state (Functional)
Stay in this IdleVRP when VRP period has not began

## 38: enter VRPVS (Functional)
when detect Vin, give VS and enter VRPVS

## 39: VRPVS state (Functional)
temporary state after receive an Vin

## 40: enter Active VRP state after VS (Functional)
set VS back to false and set value of count down variable

## 41: Active VRP state (Functional)
indicate that pacemaker is currently in a VRP period

## 42: count down in VRP (Functional)
During a VRP period, keep counting down until zero

## 43: back to Idle VRP (Functional)
when a VRP period ends, go back to Idle state

## 44: enter active VRP when VP (Functional)
When a VP is detected, start a VRP period

## 45: PVARP part (Functional)
Post-Ventricular Atrial Refractory Period Interval following a ventricular event during which atrial events would not inhibit atrial pacing or trigger ventricular pacing.

## 46: init PVARP (Functional)
set AS to false

## 47: enter Ain PVARP (Functional)
generate AS when Ain

## 48: Ain PVARP state (Functional)
When receiving an Ain signal, enter AinPVARP state, meanwhile generating an AS

## 49: reset AS (Functional)
reset AS back to false

## 50: Idle PVARP (Functional)
Stay in this IdlePVARP when PVARP period has not began

## 51: enter active state when V (Functional)
when a ventricular event is detected, start PVARP period

## 52: Active PVARP state (Functional)
indicates that pacemaker is currently in a PVARP period

## 53: back to idle PVARP state (Functional)
after PVARP period has finished, back to Idle PVARP

## 54: count down in PVARP (Functional)
During a PVARP period, count down until it ends or atrial event detected

## 55: enter PVARP AR state (Functional)
An atrial event happens during PVARP will be unsensed

## 56: PVARP AR (Functional)
indicates that an Ain happens in PVARP period thus should be unsensed

## 57: back to active PVARP (Functional)
reset AR to false, continue to count down
